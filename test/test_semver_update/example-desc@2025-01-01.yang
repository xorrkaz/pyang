module example-desc {
  yang-version 1.1;
  namespace "urn:example:desc";
  prefix ed;

  import ietf-yang-semver { prefix ysv; }

  revision 2025-01-01 {
    description "Description update.";
    ysv:version "1.0.1";
  }

  leaf name {
    type string;
    description "its name.";
  }
}
