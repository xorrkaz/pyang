module example-length {
  yang-version 1.1;
  namespace "urn:example:length";
  prefix exl;

  import ietf-yang-semver { prefix ysv; }

  revision 2024-01-01 {
    description "Initial version.";
    ysv:version "1.2.3";
  }

  leaf name {
    type string {
      length "2..10";
    }
  }
}
