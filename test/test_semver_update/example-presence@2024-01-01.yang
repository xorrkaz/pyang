module example-presence {
  yang-version 1.1;
  namespace "urn:example:presence";
  prefix ep;

  import ietf-yang-semver { prefix ysv; }

  revision 2024-01-01 {
    description "Initial version.";
    ysv:version "1.0.0";
  }

  container top {
    presence "old presence";
    leaf a {
      type string;
    }
  }
}
