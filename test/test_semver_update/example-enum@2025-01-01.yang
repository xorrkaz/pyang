module example-enum {
  yang-version 1.1;
  namespace "urn:example:enum";
  prefix ee;

  import ietf-yang-semver { prefix ysv; }

  revision 2025-01-01 {
    description "Add enum c.";
    ysv:version "1.1.0";
  }

  typedef enum-type {
    type enumeration {
      enum a;
      enum b;
      enum c;
    }
    description "Enumeration typedef.";
  }
}
