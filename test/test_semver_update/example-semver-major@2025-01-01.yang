module example-semver-major {
  yang-version 1.1;
  namespace "urn:example:semver-major";
  prefix esm;

  import ietf-yang-semver { prefix ysv; }

  revision 2025-01-01 {
    description "BC change but declared major bump.";
    ysv:version "2.0.0";
  }

  container top {
    leaf a {
      type string;
    }
    leaf b {
      type string;
    }
  }
}
