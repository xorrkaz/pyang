module example-mod {
  yang-version 1.1;
  namespace "urn:example:mod";
  prefix ex;

  import ietf-yang-semver { prefix ysv; }

  revision 2025-02-01 {
    description "Remove leaf a.";
    ysv:version "2.0.0";
  }

  container top {
    leaf b { type string; }
  }
}
