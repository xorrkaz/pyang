module example-presence {
  yang-version 1.1;
  namespace "urn:example:presence";
  prefix ep;

  import ietf-yang-semver { prefix ysv; }

  revision 2025-01-01 {
    description "Update presence statement.";
    ysv:version "1.0.1";
  }

  container top {
    presence "new presence";
    leaf a {
      type string;
    }
  }
}
