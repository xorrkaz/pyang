module example-identity {
  yang-version 1.1;
  namespace "urn:example:identity";
  prefix ei;

  import ietf-yang-semver { prefix ysv; }

  revision 2025-02-01 {
    description "Change identity description.";
    ysv:version "1.0.1";
  }

  identity base-id {
    description "identity description changed";
  }
}
