module example-yang-version {
  yang-version 1.1;
  namespace "urn:example:yang-version";
  prefix eyv;

  import ietf-yang-semver { prefix ysv; }
  import ietf-yang-revisions { prefix rev; }

  revision 2025-01-01 {
    description "Use YANG 1.1.";
    rev:non-backwards-compatible;
    ysv:version "2.0.0";
  }

  leaf name {
    type string;
  }
}
