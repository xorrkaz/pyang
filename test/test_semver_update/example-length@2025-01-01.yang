module example-length {
  yang-version 1.1;
  namespace "urn:example:length";
  prefix exl;

  import ietf-yang-semver { prefix ysv; }
  import ietf-yang-revisions { prefix rev; }

  revision 2025-01-01 {
    description "Reduce allowed string length.";
    rev:non-backwards-compatible;
    ysv:version "2.0.0";
  }

  leaf name {
    type string {
      length "2..8";
    }
  }
}
