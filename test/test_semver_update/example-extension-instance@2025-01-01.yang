module example-extension-instance {
  yang-version 1.1;
  namespace "urn:example:extension-instance";
  prefix eei;

  import ietf-yang-semver { prefix ysv; }

  revision 2025-01-01 {
    description "Change an extension instance.";
    ysv:version "1.1.0";
  }

  extension annotation {
    argument text;
  }

  eei:annotation "new annotation";
}
