module example-typedef {
  yang-version 1.1;
  namespace "urn:example:typedef";
  prefix et;

  import ietf-yang-semver { prefix ysv; }

  revision 2024-01-01 {
    description "Initial version.";
    ysv:version "1.0.0";
  }

  typedef base-string {
    type string;
  }
}
