module example-grouping {
  yang-version 1.1;
  namespace "urn:example:grouping";
  prefix eg;

  import ietf-yang-semver { prefix ysv; }

  revision 2024-01-01 {
    description "Initial version.";
    ysv:version "1.0.0";
  }

  grouping person {
    description "Person details.";
    leaf name {
      type string;
    }
  }
}
