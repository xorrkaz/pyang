module example-pattern {
  yang-version 1.1;
  namespace "urn:example:pattern";
  prefix ep;

  import ietf-yang-semver { prefix ysv; }

  revision 2025-01-01 {
    description "Pattern update.";
    ysv:version "1.0.1";
  }

  leaf name {
    type string {
      pattern "b+";
    }
  }
}
