module example-description-removal {
  yang-version 1.1;
  namespace "urn:example:description-removal";
  prefix edr;

  import ietf-yang-semver { prefix ysv; }

  revision 2024-01-01 {
    description "Initial version.";
    ysv:version "1.0.0";
  }

  leaf name {
    type string;
    description "A name.";
  }
}
