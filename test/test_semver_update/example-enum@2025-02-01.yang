module example-enum {
  yang-version 1.1;
  namespace "urn:example:enum";
  prefix ee;

  import ietf-yang-semver { prefix ysv; }

  revision 2025-02-01 {
    description "Mark enum a obsolete.";
    ysv:version "2.0.0";
  }

  typedef enum-type {
    type enumeration {
      enum a {
        status obsolete;
      }
      enum b;
    }
    description "Enumeration typedef.";
  }
}
