module bad-semver {
  yang-version 1.1;
  namespace "urn:example:bad-semver";
  prefix bs;

  import ietf-yang-semver { prefix ysv; }

  revision 2025-01-01 {
    description "Invalid semver.";
    ysv:version "1.2";
  }
}
