module example-description-removal {
  yang-version 1.1;
  namespace "urn:example:description-removal";
  prefix edr;

  import ietf-yang-semver { prefix ysv; }
  import ietf-yang-revisions { prefix rev; }

  revision 2025-01-01 {
    description "Remove a node description.";
    rev:non-backwards-compatible;
    ysv:version "2.0.0";
  }

  leaf name {
    type string;
  }
}
