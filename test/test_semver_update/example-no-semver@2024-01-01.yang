module example-no-semver {
  yang-version 1.1;
  namespace "urn:example:no-semver";
  prefix ens;

  revision 2024-01-01 {
    description "Initial version without ysv:version.";
  }

  container top {
    leaf a { type string; }
  }
}
