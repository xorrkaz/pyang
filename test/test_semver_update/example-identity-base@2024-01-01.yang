module example-identity-base {
  yang-version 1.1;
  namespace "urn:example:identity-base";
  prefix eib;

  import ietf-yang-semver { prefix ysv; }

  revision 2024-01-01 {
    description "Initial version.";
    ysv:version "1.0.0";
  }

  identity parent;
  identity child;
}
