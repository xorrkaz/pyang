module example-ref {
  yang-version 1.1;
  namespace "urn:example:ref";
  prefix er;

  import ietf-yang-semver { prefix ysv; }

  revision 2025-01-01 {
    description "Change reference.";
    ysv:version "1.1.0";
  }

  leaf name {
    type string;
    reference "RFC 2222";
  }
}
