module example-enum {
  yang-version 1.1;
  namespace "urn:example:enum";
  prefix ee;

  import ietf-yang-semver { prefix ysv; }

  revision 2024-01-01 {
    description "Initial version.";
    ysv:version "1.0.0";
  }

  typedef enum-type {
    type enumeration {
      enum a;
      enum b;
    }
    description "Enumeration typedef.";
  }
}
