module example-identity {
  yang-version 1.1;
  namespace "urn:example:identity";
  prefix ei;

  import ietf-yang-semver { prefix ysv; }

  revision 2025-04-01 {
    description "Remove obsolete retired-id.";
    ysv:version "2.1.0";
  }

  identity base-id;
}
