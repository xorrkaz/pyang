module example-grouping {
  yang-version 1.1;
  namespace "urn:example:grouping";
  prefix eg;

  import ietf-yang-semver { prefix ysv; }

  revision 2025-02-01 {
    description "Change grouping description.";
    ysv:version "1.0.1";
  }

  grouping person {
    description "Updated person details.";
    leaf name {
      type string;
    }
  }
}
