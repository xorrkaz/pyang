module example-semver-possible {
  yang-version 1.1;
  namespace "urn:example:semver-possible";
  prefix esp;

  import ietf-yang-semver { prefix ysv; }

  revision 2025-02-01 {
    description "Possible NBC with minor bump.";
    ysv:version "1.1.0";
  }

  container top {
    leaf a {
      type string;
      description "new description";
    }
  }
}
