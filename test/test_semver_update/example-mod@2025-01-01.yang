module example-mod {
  yang-version 1.1;
  namespace "urn:example:mod";
  prefix ex;

  import ietf-yang-semver { prefix ysv; }

  revision 2025-01-01 {
    description "Add leaf b.";
    ysv:version "1.3.0";
  }

  container top {
    leaf a { type string; }
    leaf b { type string; }
  }
}
