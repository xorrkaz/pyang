module example-enum-ref {
  yang-version 1.1;
  namespace "urn:example:enum-ref";
  prefix eer;

  import ietf-yang-semver { prefix ysv; }

  revision 2024-01-01 {
    description "Initial version.";
    ysv:version "1.0.0";
  }

  typedef enum-type {
    type enumeration {
      enum a {
        reference "RFC 1111";
      }
      enum b;
    }
  }
}
