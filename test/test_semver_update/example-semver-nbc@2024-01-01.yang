module example-semver-nbc {
  yang-version 1.1;
  namespace "urn:example:semver-nbc";
  prefix esn;

  import ietf-yang-semver { prefix ysv; }

  revision 2024-01-01 {
    description "Initial version.";
    ysv:version "1.2.3";
  }

  container top {
    leaf a {
      type string;
    }
  }
}
