module example-extension-instance {
  yang-version 1.1;
  namespace "urn:example:extension-instance";
  prefix eei;

  import ietf-yang-semver { prefix ysv; }

  revision 2024-01-01 {
    description "Initial version.";
    ysv:version "1.0.0";
  }

  extension annotation {
    argument text;
  }

  eei:annotation "old annotation";
}
