module example-bits {
  yang-version 1.1;
  namespace "urn:example:bits";
  prefix exb;

  import ietf-yang-semver { prefix ysv; }

  revision 2025-01-01 {
    description "Add bit notation.";
    ysv:version "1.3.0";
  }

  leaf flags {
    type bits {
      bit one;
      bit one-and-a-half;
      bit two {
        position 4;
      }
      bit three {
        position 8;
      }
    }
  }
}
