module ietf-missing-nbc {
  yang-version 1.1;
  namespace "urn:ietf:params:xml:ns:yang:ietf-missing-nbc";
  prefix imn;

  import ietf-yang-semver { prefix ysv; }

  organization
    "IETF NETMOD (Network Modeling) Working Group";
  contact
    "WG Web:   <https://datatracker.ietf.org/wg/netmod/>
     WG List:  <mailto:netmod@ietf.org>";
  description
    "Module used to test missing NBC extension on a major bump.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2025-01-01 {
    description
      "Major revision.";
    reference
      "RFC XXXX: Example.";
    ysv:version "2.0.0";
  }

  revision 2024-01-01 {
    description
      "Initial version.";
    reference
      "RFC XXXX: Example.";
    ysv:version "1.0.0";
  }
}
